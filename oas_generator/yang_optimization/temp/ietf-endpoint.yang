module ietf-endpoint {
    yang-version 1.1;
    namespace "urn:ietf:params:xml:ns:yang:ietf-endpoint";
    prefix ep;

    organization
      "QUEENS";

    contact
      "Hesham Elabd
      E-mail: hesham.abbas@queensu.ca";

    description
      "This module defines a metadata annotation named 'endpoint'
       to indicate the target schema nodes with a convention 
       endpoint name with http methods that imapct the clients
       of YANG-driven management protocols, such as NETCONF,
       RESTCONF as well as SNMP and CLI requests.

       The module defines the endpoint extension that indicates
       that data nodes based on data-definition statement cannot
       be added removed or updated except according to the
       exceptions argument.

       Copyright (c) 2023 IETF Trust and the persons identified
       as authors of the code. All rights reserved.

       Redistribution and use in source and binary forms, with
       or without modification, is permitted pursuant to, and
       subject to the license terms contained in, the Revised
       BSD License set forth in Section 4.c of the IETF Trust's
       Legal Provisions Relating to IETF Documents
       (https://trustee.ietf.org/license-info).

       This version of this YANG module is part of RFC HHHH
       (https://www.rfc-editor.org/info/rfcHHHH); see the RFC
       itself for full legal notices.

       The key words 'MUST', 'MUST NOT', 'REQUIRED', 'SHALL',
       'SHALL NOT', 'SHOULD', 'SHOULD NOT', 'RECOMMENDED',
       'NOT RECOMMENDED', 'MAY', and 'OPTIONAL' in this document
       are to be interpreted as described in BCP 14 (RFC 2119)
       (RFC 8174) when, and only when, they appear in all
       capitals, as shown here.";

    revision 2023-12-01 {
      description
        "Initial revision.";
      reference
        "RFC XXXX: YANG Extension and Metadata Annotation for Endpoint Flag";
    }

    extension endpoint {
      argument name;
      description
        "The 'endpoint' extension as a substatement to a data
         definition statement indicates that data nodes based on
         the parent statement MUST NOT be added, removed or
         updated by management protocols, such as NETCONF,
         RESTCONF or other management operations (e.g., SNMP
         and CLI requests) except when indicated by the
         exceptions argument.";
    }
  }
