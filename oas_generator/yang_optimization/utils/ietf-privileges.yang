module ietf-privileges {
    yang-version 1.1;
    namespace "urn:ietf:params:xml:ns:yang:ietf-privileges";
    prefix pr;

    organization
      "QUEENS";

    contact
      "Hesham Elabd
      E-mail: hesham.abbas@queensu.ca";

    description
      "This module defines a metadata annotation named 'privileges'
       to indicate the accessibility of a particular instantiated
       data node. Any instantiated data node marked with
       privileges='true' by the server is full access to the clients
       of YANG-driven management protocols, such as NETCONF,
       RESTCONF as well as SNMP and CLI requests.

       The module defines the privileges extension that indicates
       that data nodes based on data-definition statement cannot
       be retrived, added, updated or removed except according to the
       operations argument.

       Copyright (c) 2024 IETF Trust and the persons identified
       as authors of the code. All rights reserved.

       Redistribution and use in source and binary forms, with
       or without modification, is permitted pursuant to, and
       subject to the license terms contained in, the Revised
       BSD License set forth in Section 4.c of the IETF Trust's
       Legal Provisions Relating to IETF Documents
       (https://trustee.ietf.org/license-info).

       This version of this YANG module is part of RFC HHHH
       (https://www.rfc-editor.org/info/rfcHHHH); see the RFC
       itself for full legal notices.

       The key words 'MUST', 'MUST NOT', 'REQUIRED', 'SHALL',
       'SHALL NOT', 'SHOULD', 'SHOULD NOT', 'RECOMMENDED',
       'NOT RECOMMENDED', 'MAY', and 'OPTIONAL' in this document
       are to be interpreted as described in BCP 14 (RFC 2119)
       (RFC 8174) when, and only when, they appear in all
       capitals, as shown here.";

    revision 2024-01-01 {
      description
        "Initial revision.";
      reference
        "RFC XXXX: YANG Extension and Metadata Annotation for providing Privileges";
    }

    extension privileges {
      argument operations;
      description
        "The 'privileges' extension as a substatement to a data
         definition statement indicates that data nodes based on
         the parent statement MUST NOT be added, removed or
         updated by management protocols, such as NETCONF,
         RESTCONF or other management operations (e.g., SNMP
         and CLI requests) except when indicated by the
         operations argument.

        
         The argument consists of a list of operations permitted for 
         the specified node, with other operations being restricted by
         the privileges extension.
         - create: allows users to create instances of the data node
         - update: allows users to modify instances of the data node
         - patch: allows users to partially modify instance of the data node
         - delete: allows users to delete instances of the data node
         - fetch: allows users to retrieve instances of the data node

         To restrict all user access, exclude the argument;

         To allow only update and delete user access, provide
         the string 'update delete' for the 'operations' parameter.

         Equivalent YANG definition for this extension:

         leaf privileges {
           type bits {
             bit create;
             bit update;
             bit patch;
             bit delete;
             bit fetch;
           }
           default '';
         }
        
        ";
    }
  }
